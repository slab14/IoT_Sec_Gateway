module switchDemo {
    yang-version 1;
    namespace "edu:cmu:slab:yang:switchDemo";
    prefix "switchDemo";

    revision "2018-06-27" {
        description "Initial revision of switchDemo model -- getting notifications from packets";
    }

}
